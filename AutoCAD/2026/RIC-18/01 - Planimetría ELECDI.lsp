;;; ============================================================================
;;; Programa de inserción de bloques RIC-18 (versión autónoma)
;;; Basado en las definiciones exportadas desde tu archivo original.
;;; Compatible con AutoCAD para Mac y Windows.
;;; Comando principal: RIC-18
;;; ============================================================================

;;; ------------------------------------------------------------
;;; 1. DEFINICIONES DE LOS BLOQUES (exportadas desde tu archivo)
;;; ------------------------------------------------------------
(setq *bloques* '(
  ("CA"
    (
      ((0 . "ARC") (100 . "AcDbEntity") (67 . 0) (8 . "0") (100 . "AcDbCircle") (10 707873.0 1.67176e+06 0.0) (40 . 66945.4) (210 0.0 0.0 1.0) (100 . "AcDbArc") (50 . 4.02681) (51 . 5.8108))
    ))
  ("CC"
    (
      ((0 . "LINE") (100 . "AcDbEntity") (67 . 0) (8 . "0") (100 . "AcDbLine") (10 564197.0 1.55038e+06 0.0) (11 666597.0 1.55038e+06 0.0) (210 0.0 0.0 1.0))
      ((0 . "LINE") (100 . "AcDbEntity") (67 . 0) (8 . "0") (100 . "AcDbLine") (10 786413.0 1.55038e+06 0.0) (11 681226.0 1.55038e+06 0.0) (210 0.0 0.0 1.0))
    ))
  ("TOM_PRT"
    (
      ((0 . "LINE") (100 . "AcDbEntity") (67 . 0) (8 . "0") (100 . "AcDbLine") (10 685405.0 1.46404e+06 0.0) (11 685405.0 1.52393e+06 0.0) (210 0.0 0.0 1.0))
      ((0 . "LINE") (100 . "AcDbEntity") (67 . 0) (8 . "0") (100 . "AcDbLine") (10 668531.0 1.48227e+06 0.0) (11 703990.0 1.48227e+06 0.0) (210 0.0 0.0 1.0))
      ((0 . "LINE") (100 . "AcDbEntity") (67 . 0) (8 . "0") (100 . "AcDbLine") (10 676129.0 1.47552e+06 0.0) (11 695970.0 1.47552e+06 0.0) (210 0.0 0.0 1.0))
      ((0 . "LINE") (100 . "AcDbEntity") (67 . 0) (8 . "0") (100 . "AcDbLine") (10 680601.0 1.47036e+06 0.0) (11 691790.0 1.47036e+06 0.0) (210 0.0 0.0 1.0))
    ))
  ("TT_SV"
    (
      ((0 . "LINE") (100 . "AcDbEntity") (67 . 0) (8 . "0") (100 . "AcDbLine") (10 660878.0 1.37517e+06 0.0) (11 710745.0 1.37517e+06 0.0) (210 0.0 0.0 1.0))
      ((0 . "LINE") (100 . "AcDbEntity") (67 . 0) (8 . "0") (100 . "AcDbLine") (10 671622.0 1.36302e+06 0.0) (11 700001.0 1.36302e+06 0.0) (210 0.0 0.0 1.0))
      ((0 . "LINE") (100 . "AcDbEntity") (67 . 0) (8 . "0") (100 . "AcDbLine") (10 694123.0 1.3533e+06 0.0) (11 677501.0 1.3533e+06 0.0) (210 0.0 0.0 1.0))
    ))
  ("ART_FLR_N"
    (
      ((0 . "MTEXT") (100 . "AcDbEntity") (67 . 0) (8 . "0") (100 . "AcDbMText") (10 787586.0 1.25803e+06 0.0) (40 . 16780.7) (41 . 38853.2) (46 . 0.0) (71 . 1) (72 . 5) (1 . "n") (7 . "Standard") (210 0.0 0.0 1.0) (11 1.0 0.0 0.0) (42 . 9878.41) (43 . 16780.7) (50 . 0.0) (73 . 1) (44 . 1.0))
    ))
  ("BT"
    (
      ((0 . "LINE") (100 . "AcDbEntity") (67 . 0) (8 . "0") (100 . "AcDbLine") (10 630650.0 1.14726e+06 0.0) (11 677430.0 1.14726e+06 0.0) (210 0.0 0.0 1.0))
      ((0 . "LINE") (100 . "AcDbEntity") (67 . 0) (8 . "0") (100 . "AcDbLine") (10 676960.0 1.15119e+06 0.0) (11 676960.0 1.14332e+06 0.0) (210 0.0 0.0 1.0))
      ((0 . "LINE") (100 . "AcDbEntity") (67 . 0) (8 . "0") (100 . "AcDbLine") (10 696168.0 1.15701e+06 0.0) (11 696168.0 1.1375e+06 0.0) (210 0.0 0.0 1.0))
      ((0 . "LINE") (100 . "AcDbEntity") (67 . 0) (8 . "0") (100 . "AcDbLine") (10 684378.0 1.14726e+06 0.0) (11 726143.0 1.14726e+06 0.0) (210 0.0 0.0 1.0))
    ))
  ("BCN"
    (
      ((0 . "LINE") (100 . "AcDbEntity") (67 . 0) (8 . "0") (100 . "AcDbLine") (10 -273.362 21523.0 0.0) (11 -118.693 10530.7 0.0) (210 0.0 0.0 1.0))
      ((0 . "LINE") (100 . "AcDbEntity") (67 . 0) (8 . "0") (100 . "AcDbLine") (10 288.928 -17994.5 0.0) (11 288.928 -9545.36 0.0) (210 0.0 0.0 1.0))
      ((0 . "LINE") (100 . "AcDbEntity") (67 . 0) (8 . "0") (100 . "AcDbLine") (10 4651.82 9545.36 0.0) (11 28265.2 23619.4 0.0) (210 0.0 0.0 1.0))
      ((0 . "LINE") (100 . "AcDbEntity") (67 . 0) (8 . "0") (100 . "AcDbLine") (10 28265.2 23619.4 0.0) (11 28265.2 -20195.2 0.0) (210 0.0 0.0 1.0))
      ((0 . "LINE") (100 . "AcDbEntity") (67 . 0) (8 . "0") (100 . "AcDbLine") (10 28265.2 -20195.2 0.0) (11 4651.82 -9545.36 0.0) (210 0.0 0.0 1.0))
    ))
  
  ("CLN_AGUA"
    (
      ((0 . "INSERT") (100 . "AcDbEntity") (67 . 0) (8 . "0") (100 . "AcDbBlockReference") (2 . "CLNT_AGUA") (10 671979.0 1.02926e+06 0.0) (41 . 1.0) (42 . 1.0) (43 . 1.0) (50 . 0.0) (70 . 0) (71 . 0) (44 . 0.0) (45 . 0.0) (210 0.0 0.0 1.0))
    ))
  ("ARR_DRV"
    (
      ((0 . "LINE") (100 . "AcDbEntity") (67 . 0) (8 . "0") (100 . "AcDbLine") (10 661983.0 961005.0 0.0) (11 689414.0 961005.0 0.0) (210 0.0 0.0 1.0))
      ((0 . "HATCH") (100 . "AcDbEntity") (67 . 0) (8 . "0") (100 . "AcDbHatch") (10 0.0 0.0 0.0) (210 0.0 0.0 1.0) (2 . "SOLID,_O") (70 . 1) (71 . 1) (91 . 1) (92 . 7) (72 . 1) (73 . 1) (93 . 2) (10 666973.0 968068.0 0.0) (42 . 1.0) (10 681100.0 968068.0 0.0) (42 . 1.0) (97 . 1) (75 . 1) (76 . 1) (47 . 0.0619007) (98 . 1) (10 673620.0 968899.0 0.0) (450 . 1) (451 . 0) (460 . 0.0) (461 . 0.0) (452 . 0) (462 . 1.0) (453 . 2) (463 . 0.0) (63 . 250) (421 . 3355443) (463 . 1.0) (63 . 250) (421 . 3355443) (470 . "SPHERICAL"))
      ((0 . "CIRCLE") (100 . "AcDbEntity") (67 . 0) (8 . "0") (100 . "AcDbCircle") (10 674036.0 968068.0 0.0) (40 . 7063.41) (210 0.0 0.0 1.0))
    ))
  ("BNDJ"
    (
      ((0 . "LINE") (100 . "AcDbEntity") (67 . 0) (8 . "0") (100 . "AcDbLine") (10 572053.0 853777.0 0.0) (11 624154.0 853777.0 0.0) (210 0.0 0.0 1.0))
      ((0 . "LINE") (100 . "AcDbEntity") (67 . 0) (8 . "0") (100 . "AcDbLine") (10 658706.0 853229.0 0.0) (11 719582.0 853229.0 0.0) (210 0.0 0.0 1.0))
      ((0 . "LINE") (100 . "AcDbEntity") (67 . 0) (8 . "0") (100 . "AcDbLine") (10 737681.0 852681.0 0.0) (11 791428.0 852681.0 0.0) (210 0.0 0.0 1.0))
      ((0 . "LINE") (100 . "AcDbEntity") (67 . 0) (8 . "0") (100 . "AcDbLine") (10 808444.0 852136.0 0.0) (11 868772.0 852136.0 0.0) (210 0.0 0.0 1.0))
      ((0 . "LINE") (100 . "AcDbEntity") (67 . 0) (8 . "0") (100 . "AcDbLine") (10 501319.0 833495.0 0.0) (11 545194.0 833495.0 0.0) (210 0.0 0.0 1.0))
      ((0 . "LINE") (100 . "AcDbEntity") (67 . 0) (8 . "0") (100 . "AcDbLine") (10 572067.0 832399.0 0.0) (11 623620.0 832399.0 0.0) (210 0.0 0.0 1.0))
      ((0 . "LINE") (100 . "AcDbEntity") (67 . 0) (8 . "0") (100 . "AcDbLine") (10 658172.0 833495.0 0.0) (11 719597.0 833495.0 0.0) (210 0.0 0.0 1.0))
      ((0 . "LINE") (100 . "AcDbEntity") (67 . 0) (8 . "0") (100 . "AcDbLine") (10 738244.0 832947.0 0.0) (11 790894.0 832947.0 0.0) (210 0.0 0.0 1.0))
      ((0 . "LINE") (100 . "AcDbEntity") (67 . 0) (8 . "0") (100 . "AcDbLine") (10 808444.0 832399.0 0.0) (11 869321.0 832399.0 0.0) (210 0.0 0.0 1.0))
    ))
  ("CBL_CONC"
    (
      ((0 . "LINE") (100 . "AcDbEntity") (67 . 0) (8 . "0") (100 . "AcDbLine") (10 652654.0 766975.0 0.0) (11 730574.0 766975.0 0.0) (210 0.0 0.0 1.0))
      ((0 . "LINE") (100 . "AcDbEntity") (67 . 0) (8 . "0") (100 . "AcDbLine") (10 651136.0 754330.0 0.0) (11 662774.0 754330.0 0.0) (210 0.0 0.0 1.0))
      ((0 . "LINE") (100 . "AcDbEntity") (67 . 0) (8 . "0") (100 . "AcDbLine") (10 685037.0 767987.0 0.0) (11 685037.0 767987.0 0.0) (210 0.0 0.0 1.0))
      ((0 . "LINE") (100 . "AcDbEntity") (67 . 0) (8 . "0") (100 . "AcDbLine") (10 665701.0 754286.0 0.0) (11 681510.0 754286.0 0.0) (210 0.0 0.0 1.0))
      ((0 . "LINE") (100 . "AcDbEntity") (67 . 0) (8 . "0") (100 . "AcDbLine") (10 685038.0 754155.0 0.0) (11 692877.0 754155.0 0.0) (210 0.0 0.0 1.0))
      ((0 . "LINE") (100 . "AcDbEntity") (67 . 0) (8 . "0") (100 . "AcDbLine") (10 699410.0 753763.0 0.0) (11 708686.0 753763.0 0.0) (210 0.0 0.0 1.0))
      ((0 . "LINE") (100 . "AcDbEntity") (67 . 0) (8 . "0") (100 . "AcDbLine") (10 712089.0 753762.0 0.0) (11 719929.0 753762.0 0.0) (210 0.0 0.0 1.0))
      ((0 . "LINE") (100 . "AcDbEntity") (67 . 0) (8 . "0") (100 . "AcDbLine") (10 724502.0 753762.0 0.0) (11 731949.0 753762.0 0.0) (210 0.0 0.0 1.0))
    ))
  ("CBL_FLEX"
    (
      ((0 . "ARC") (100 . "AcDbEntity") (67 . 0) (8 . "0") (100 . "AcDbCircle") (10 615756.0 709788.0 0.0) (40 . 19095.2) (210 0.0 0.0 1.0) (100 . "AcDbArc") (50 . 6.10288) (51 . 2.87434))
      ((0 . "ARC") (100 . "AcDbEntity") (67 . 0) (8 . "0") (100 . "AcDbCircle") (10 653327.0 705031.0 0.0) (40 . 18832.8) (210 0.0 0.0 1.0) (100 . "AcDbArc") (50 . 3.07078) (51 . 0.351616))
      ((0 . "ARC") (100 . "AcDbEntity") (67 . 0) (8 . "0") (100 . "AcDbCircle") (10 689978.0 710930.0 0.0) (40 . 18978.9) (210 0.0 0.0 1.0) (100 . "AcDbArc") (50 . 5.93884) (51 . 3.11063))
      ((0 . "ARC") (100 . "AcDbEntity") (67 . 0) (8 . "0") (100 . "AcDbCircle") (10 724418.0 705443.0 0.0) (40 . 16601.1) (210 0.0 0.0 1.0) (100 . "AcDbArc") (50 . 3.19706) (51 . 0.0554666))
      ((0 . "ARC") (100 . "AcDbEntity") (67 . 0) (8 . "0") (100 . "AcDbCircle") (10 756280.0 705811.0 0.0) (40 . 15296.3) (210 0.0 0.0 1.0) (100 . "AcDbArc") (50 . 6.24708) (51 . 3.10548))
      ((0 . "LINE") (100 . "AcDbEntity") (67 . 0) (8 . "0") (100 . "AcDbLine") (10 564556.0 712254.0 0.0) (11 564556.0 728083.0 0.0) (210 0.0 0.0 1.0))
      ((0 . "LINE") (100 . "AcDbEntity") (67 . 0) (8 . "0") (100 . "AcDbLine") (10 771566.0 705259.0 0.0) (11 771566.0 687957.0 0.0) (210 0.0 0.0 1.0))
    ))
  ("CJ_DRV"
    (
      ((0 . "CIRCLE") (100 . "AcDbEntity") (67 . 0) (8 . "0") (100 . "AcDbCircle") (10 674739.0 644131.0 0.0) (40 . 18215.0) (210 0.0 0.0 1.0))
    ))
  ("CMR_PASO"
    (
    ))
  ("CMR_REGISTRO"
    (
      ((0 . "CIRCLE") (100 . "AcDbEntity") (67 . 0) (8 . "0") (100 . "AcDbCircle") (10 675262.0 522365.0 0.0) (40 . 11835.4) (210 0.0 0.0 1.0))
    ))
  ("LIN_N_CON"
    (
      ((0 . "LINE") (100 . "AcDbEntity") (67 . 0) (8 . "0") (100 . "AcDbLine") (10 -81929.0 -216.619 0.0) (11 85396.9 -216.619 0.0) (210 0.0 0.0 1.0))
      ((0 . "MTEXT") (100 . "AcDbEntity") (67 . 0) (8 . "0") (100 . "AcDbMText") (10 55471.6 -216.619 0.0) (40 . 16780.7) (41 . 29925.2) (46 . 0.0) (71 . 1) (72 . 5) (1 . "n") (7 . "Standard") (210 0.0 0.0 1.0) (11 1.0 0.0 0.0) (42 . 9878.41) (43 . 16780.7) (50 . 0.0) (73 . 1) (44 . 1.0))
    ))
  ("CANAL"
    (
    ))
  ("EMP"
    (
      ((0 . "MTEXT") (100 . "AcDbEntity") (67 . 0) (8 . "0") (100 . "AcDbMText") (10 -7182.88 8135.89 0.0) (40 . 16780.7) (41 . 15323.5) (46 . 0.0) (71 . 1) (72 . 5) (1 . "E") (7 . "Standard") (210 0.0 0.0 1.0) (11 1.0 0.0 0.0) (42 . 12522.6) (43 . 16780.7) (50 . 0.0) (73 . 1) (44 . 1.0))
    ))
  ("ENCH_ALUM"
    (
      ((0 . "HATCH") (100 . "AcDbEntity") (67 . 0) (8 . "0") (62 . 250) (100 . "AcDbHatch") (10 0.0 0.0 0.0) (210 0.0 0.0 1.0) (2 . "SOLID") (70 . 1) (71 . 0) (91 . 2) (92 . 7) (72 . 1) (73 . 1) (93 . 3) (10 0.0 50010.0 0.0) (42 . 0.42919) (10 -17144.8 31970.3 0.0) (42 . 0.0) (10 0.0 31970.3 0.0) (42 . 0.0) (97 . 0) (92 . 7) (72 . 1) (73 . 1) (93 . 3) (10 0.0 50010.0 0.0) (42 . 0.0) (10 0.0 31970.3 0.0) (42 . 0.0) (10 17144.8 31970.3 0.0) (42 . 0.42919) (97 . 0) (75 . 1) (76 . 1) (47 . 0.206525) (98 . 2) (10 -2285.68 36792.8 0.0) (10 8807.95 36792.8 0.0) (450 . 0) (451 . 0) (460 . 0.0) (461 . 0.0) (452 . 0) (462 . 1.0) (453 . 2) (463 . 0.0) (63 . 5) (421 . 255) (463 . 1.0) (63 . 2) (421 . 16776960) (470 . "LINEAR"))
      ((0 . "LINE") (100 . "AcDbEntity") (67 . 0) (8 . "0") (100 . "AcDbLine") (10 0.0 0.0 0.0) (11 0.0 59353.4 0.0) (210 0.0 0.0 1.0))
      ((0 . "ARC") (100 . "AcDbEntity") (67 . 0) (8 . "0") (100 . "AcDbCircle") (10 0.0 32843.1 0.0) (40 . 17167.0) (210 0.0 0.0 1.0) (100 . "AcDbArc") (50 . 6.23232) (51 . 3.19245))
      ((0 . "LINE") (100 . "AcDbEntity") (67 . 0) (8 . "0") (100 . "AcDbLine") (10 -17144.8 31970.3 0.0) (11 17144.8 31970.3 0.0) (210 0.0 0.0 1.0))
    ))
  ("ENCH_DOBLE_ALUM"
    (
      ((0 . "HATCH") (100 . "AcDbEntity") (67 . 0) (8 . "0") (62 . 250) (100 . "AcDbHatch") (10 0.0 0.0 0.0) (210 0.0 0.0 1.0) (2 . "SOLID") (70 . 1) (71 . 0) (91 . 2) (92 . 7) (72 . 1) (73 . 1) (93 . 3) (10 0.0 50010.0 0.0) (42 . 0.42919) (10 -17144.8 31970.3 0.0) (42 . 0.0) (10 0.0 31970.3 0.0) (42 . 0.0) (97 . 0) (92 . 7) (72 . 1) (73 . 1) (93 . 3) (10 0.0 31970.3 0.0) (42 . 0.0) (10 17144.8 31970.3 0.0) (42 . 0.42919) (10 0.0 50010.0 0.0) (42 . 0.0) (97 . 0) (75 . 1) (76 . 1) (47 . 0.197401) (98 . 2) (10 -5750.25 39872.3 0.0) (10 4853.28 39872.3 0.0) (450 . 0) (451 . 0) (460 . 0.0) (461 . 0.0) (452 . 0) (462 . 1.0) (453 . 2) (463 . 0.0) (63 . 5) (421 . 255) (463 . 1.0) (63 . 2) (421 . 16776960) (470 . "LINEAR"))
      ((0 . "LINE") (100 . "AcDbEntity") (67 . 0) (8 . "0") (100 . "AcDbLine") (10 0.0 0.0 0.0) (11 0.0 59353.4 0.0) (210 0.0 0.0 1.0))
      ((0 . "ARC") (100 . "AcDbEntity") (67 . 0) (8 . "0") (100 . "AcDbCircle") (10 0.0 32843.1 0.0) (40 . 17167.0) (210 0.0 0.0 1.0) (100 . "AcDbArc") (50 . 6.23232) (51 . 3.19245))
      ((0 . "LINE") (100 . "AcDbEntity") (67 . 0) (8 . "0") (100 . "AcDbLine") (10 -17144.8 31970.3 0.0) (11 17144.8 31970.3 0.0) (210 0.0 0.0 1.0))
      ((0 . "LINE") (100 . "AcDbEntity") (67 . 0) (8 . "0") (100 . "AcDbLine") (10 -8783.33 57834.7 0.0) (11 -8783.33 47592.9 0.0) (210 0.0 0.0 1.0))
      ((0 . "LINE") (100 . "AcDbEntity") (67 . 0) (8 . "0") (100 . "AcDbLine") (10 8881.78 57834.7 0.0) (11 8881.78 47533.8 0.0) (210 0.0 0.0 1.0))
    ))
  ("ENCH_CALEF"
    (
      ((0 . "HATCH") (100 . "AcDbEntity") (67 . 0) (8 . "0") (62 . 0) (100 . "AcDbHatch") (10 0.0 0.0 0.0) (210 0.0 0.0 1.0) (2 . "ANSI31") (70 . 0) (71 . 0) (91 . 2) (92 . 7) (72 . 1) (73 . 1) (93 . 3) (10 0.0 50010.0 0.0) (42 . 0.42919) (10 -17144.8 31970.3 0.0) (42 . 0.0) (10 0.0 31970.3 0.0) (42 . 0.0) (97 . 0) (92 . 7) (72 . 1) (73 . 1) (93 . 3) (10 0.0 50010.0 0.0) (42 . 0.0) (10 0.0 31970.3 0.0) (42 . 0.0) (10 17144.8 31970.3 0.0) (42 . 0.42919) (97 . 0) (75 . 1) (76 . 1) (52 . 0.0) (41 . 2000.0) (77 . 0) (78 . 1) (53 . 0.785398) (43 . -733049.0) (44 . 112455.0) (45 . -4490.13) (46 . 4490.13) (79 . 0) (47 . 0.100726) (98 . 2) (10 -6246.99 38275.9 0.0) (10 9612.26 41205.0 0.0))
      ((0 . "LINE") (100 . "AcDbEntity") (67 . 0) (8 . "0") (100 . "AcDbLine") (10 0.0 0.0 0.0) (11 0.0 59353.4 0.0) (210 0.0 0.0 1.0))
      ((0 . "ARC") (100 . "AcDbEntity") (67 . 0) (8 . "0") (100 . "AcDbCircle") (10 0.0 32843.1 0.0) (40 . 17167.0) (210 0.0 0.0 1.0) (100 . "AcDbArc") (50 . 6.23232) (51 . 3.19245))
      ((0 . "LINE") (100 . "AcDbEntity") (67 . 0) (8 . "0") (100 . "AcDbLine") (10 -17144.8 31970.3 0.0) (11 17144.8 31970.3 0.0) (210 0.0 0.0 1.0))
    ))
  ("ENCH_FRZA_MONO"
    (
      ((0 . "MTEXT") (100 . "AcDbEntity") (67 . 0) (8 . "0") (100 . "AcDbMText") (10 -157390.0 18505.9 0.0) (40 . 16780.7) (41 . 33301.1) (46 . 0.0) (71 . 1) (72 . 5) (1 . "3") (7 . "Standard") (210 0.0 0.0 1.0) (11 1.0 0.0 0.0) (42 . 10988.7) (43 . 17147.0) (50 . 0.0) (73 . 1) (44 . 1.0))
      ((0 . "LINE") (100 . "AcDbEntity") (67 . 0) (8 . "0") (100 . "AcDbLine") (10 -166893.0 0.0 0.0) (11 0.0 0.0 0.0) (210 0.0 0.0 1.0))
      ((0 . "HATCH") (100 . "AcDbEntity") (67 . 0) (8 . "0") (62 . 0) (100 . "AcDbHatch") (10 0.0 0.0 0.0) (210 0.0 0.0 1.0) (2 . "ANSI31") (70 . 0) (71 . 1) (91 . 2) (92 . 7) (72 . 1) (73 . 1) (93 . 3) (10 0.0 50010.0 0.0) (42 . 0.42919) (10 -17144.8 31970.3 0.0) (42 . 0.0) (10 0.0 31970.3 0.0) (42 . 0.0) (97 . 3) (92 . 7) (72 . 1) (73 . 1) (93 . 3) (10 9.09495e-13 31970.3 0.0) (42 . 0.0) (10 17144.8 31970.3 0.0) (42 . 0.42919) (10 0.0 50010.0 0.0) (42 . 0.0) (97 . 3) (75 . 1) (76 . 1) (52 . 0.0) (41 . 2000.0) (77 . 0) (78 . 1) (53 . 0.785398) (43 . -733049.0) (44 . 234594.0) (45 . -4490.13) (46 . 4490.13) (79 . 0) (47 . 0.100726) (98 . 2) (10 -5266.75 42998.8 0.0) (10 6906.99 38942.2 0.0))
      ((0 . "LINE") (100 . "AcDbEntity") (67 . 0) (8 . "0") (100 . "AcDbLine") (10 0.0 0.0 0.0) (11 0.0 59353.4 0.0) (210 0.0 0.0 1.0))
      ((0 . "ARC") (100 . "AcDbEntity") (67 . 0) (8 . "0") (100 . "AcDbCircle") (10 0.0 32843.1 0.0) (40 . 17167.0) (210 0.0 0.0 1.0) (100 . "AcDbArc") (50 . 6.23232) (51 . 3.19245))
      ((0 . "LINE") (100 . "AcDbEntity") (67 . 0) (8 . "0") (100 . "AcDbLine") (10 -17144.8 31970.3 0.0) (11 17144.8 31970.3 0.0) (210 0.0 0.0 1.0))
    ))
  ("ENCH_FRZA_TRIF"
    (
      ((0 . "MTEXT") (100 . "AcDbEntity") (67 . 0) (8 . "0") (100 . "AcDbMText") (10 -187350.0 17682.6 0.0) (40 . 16780.7) (41 . 14974.9) (46 . 0.0) (71 . 1) (72 . 5) (1 . "n") (7 . "Standard") (210 0.0 0.0 1.0) (11 1.0 0.0 0.0) (42 . 9878.41) (43 . 16780.7) (50 . 0.0) (73 . 1) (44 . 1.0))
      ((0 . "LINE") (100 . "AcDbEntity") (67 . 0) (8 . "0") (100 . "AcDbLine") (10 -166893.0 0.0 0.0) (11 0.0 0.0 0.0) (210 0.0 0.0 1.0))
      ((0 . "HATCH") (100 . "AcDbEntity") (67 . 0) (8 . "0") (62 . 0) (100 . "AcDbHatch") (10 0.0 0.0 0.0) (210 0.0 0.0 1.0) (2 . "ANSI31") (70 . 0) (71 . 0) (91 . 2) (92 . 7) (72 . 1) (73 . 1) (93 . 3) (10 0.0 50010.0 0.0) (42 . 0.42919) (10 -17144.8 31970.3 0.0) (42 . 0.0) (10 0.0 31970.3 0.0) (42 . 0.0) (97 . 0) (92 . 7) (72 . 1) (73 . 1) (93 . 3) (10 0.0 31970.3 0.0) (42 . 0.0) (10 17144.8 31970.3 0.0) (42 . 0.42919) (10 0.0 50010.0 0.0) (42 . 0.0) (97 . 0) (75 . 1) (76 . 1) (52 . 0.0) (41 . 2000.0) (77 . 0) (78 . 1) (53 . 0.785398) (43 . -733049.0) (44 . 374174.0) (45 . -4490.13) (46 . 4490.13) (79 . 0) (47 . 0.100726) (98 . 2) (10 -4618.08 43835.9 0.0) (10 6203.02 41131.5 0.0))
      ((0 . "LINE") (100 . "AcDbEntity") (67 . 0) (8 . "0") (100 . "AcDbLine") (10 0.0 0.0 0.0) (11 0.0 59353.4 0.0) (210 0.0 0.0 1.0))
      ((0 . "ARC") (100 . "AcDbEntity") (67 . 0) (8 . "0") (100 . "AcDbCircle") (10 0.0 32843.1 0.0) (40 . 17167.0) (210 0.0 0.0 1.0) (100 . "AcDbArc") (50 . 6.23232) (51 . 3.19245))
      ((0 . "LINE") (100 . "AcDbEntity") (67 . 0) (8 . "0") (100 . "AcDbLine") (10 -17144.8 31970.3 0.0) (11 17144.8 31970.3 0.0) (210 0.0 0.0 1.0))
    ))
  ("ENCH_ESPEC"
    (
      ((0 . "HATCH") (100 . "AcDbEntity") (67 . 0) (8 . "0") (62 . 0) (100 . "AcDbHatch") (10 0.0 0.0 0.0) (210 0.0 0.0 1.0) (2 . "SOLID") (70 . 1) (71 . 1) (91 . 2) (92 . 23) (72 . 1) (73 . 1) (93 . 3) (10 -17144.8 31970.3 0.0) (42 . 0.0) (10 0.0 31970.3 0.0) (42 . 0.0) (10 0.0 50010.0 0.0) (42 . 0.42919) (97 . 3) (92 . 23) (72 . 1) (73 . 1) (93 . 3) (10 17144.8 31970.3 0.0) (42 . 0.42919) (10 0.0 50010.0 0.0) (42 . 0.0) (10 -9.09495e-13 31970.3 0.0) (42 . 0.0) (97 . 3) (75 . 1) (76 . 1) (47 . 0.037039) (98 . 4) (10 -5942.37 42600.1 0.0) (10 8233.37 37130.5 0.0) (10 -7326.91 40635.1 0.0) (10 7552.11 38606.8 0.0) (450 . 0) (451 . 0) (460 . 0.0) (461 . 0.0) (452 . 0) (462 . 1.0) (453 . 2) (463 . 0.0) (63 . 5) (421 . 255) (463 . 1.0) (63 . 2) (421 . 16776960) (470 . "LINEAR"))
      ((0 . "HATCH") (100 . "AcDbEntity") (67 . 0) (8 . "0") (62 . 0) (100 . "AcDbHatch") (10 0.0 0.0 0.0) (210 0.0 0.0 1.0) (2 . "SOLID,_O") (70 . 1) (71 . 0) (91 . 2) (92 . 7) (72 . 1) (73 . 1) (93 . 3) (10 -17144.8 31970.3 0.0) (42 . 0.0) (10 0.0 31970.3 0.0) (42 . 0.0) (10 0.0 50010.0 0.0) (42 . 0.42919) (97 . 0) (92 . 7) (72 . 1) (73 . 1) (93 . 3) (10 0.0 31970.3 0.0) (42 . 0.0) (10 17144.8 31970.3 0.0) (42 . 0.42919) (10 0.0 50010.0 0.0) (42 . 0.0) (97 . 0) (75 . 1) (76 . 1) (47 . 0.0587932) (98 . 2) (10 -7772.09 39916.7 0.0) (10 4860.39 39916.7 0.0) (450 . 1) (451 . 0) (460 . 0.0) (461 . 0.0) (452 . 0) (462 . 1.0) (453 . 2) (463 . 0.0) (63 . 7) (421 . 16777215) (463 . 1.0) (63 . 7) (421 . 16777215) (470 . "LINEAR"))
      ((0 . "LINE") (100 . "AcDbEntity") (67 . 0) (8 . "0") (100 . "AcDbLine") (10 0.0 0.0 0.0) (11 0.0 59353.4 0.0) (210 0.0 0.0 1.0))
      ((0 . "ARC") (100 . "AcDbEntity") (67 . 0) (8 . "0") (100 . "AcDbCircle") (10 0.0 32843.1 0.0) (40 . 17167.0) (210 0.0 0.0 1.0) (100 . "AcDbArc") (50 . 6.23232) (51 . 3.19245))
      ((0 . "LINE") (100 . "AcDbEntity") (67 . 0) (8 . "0") (100 . "AcDbLine") (10 -17144.8 31970.3 0.0) (11 17144.8 31970.3 0.0) (210 0.0 0.0 1.0))
    ))
  ("GNRD"
    (
      ((0 . "MTEXT") (100 . "AcDbEntity") (67 . 0) (8 . "0") (100 . "AcDbMText") (10 -28820.9 31200.5 0.0) (40 . 60410.5) (41 . 19372.2) (46 . 0.0) (71 . 1) (72 . 5) (1 . "G") (7 . "Standard") (210 0.0 0.0 1.0) (11 1.0 0.0 0.0) (42 . 55877.7) (43 . 62470.9) (50 . 0.0) (73 . 1) (44 . 1.0))
    ))
  ("INT1_EF"
    (
      ((0 . "LINE") (100 . "AcDbEntity") (67 . 0) (8 . "0") (100 . "AcDbLine") (10 0.0 0.0 0.0) (11 0.0 53890.6 0.0) (210 0.0 0.0 1.0))
      ((0 . "LINE") (100 . "AcDbEntity") (67 . 0) (8 . "0") (100 . "AcDbLine") (10 0.0 53890.6 0.0) (11 27048.1 53890.6 0.0) (210 0.0 0.0 1.0))
    ))
  ("INT2_EF"
    (
      ((0 . "LINE") (100 . "AcDbEntity") (67 . 0) (8 . "0") (100 . "AcDbLine") (10 0.0 0.0 0.0) (11 0.0 72164.2 0.0) (210 0.0 0.0 1.0))
      ((0 . "LINE") (100 . "AcDbEntity") (67 . 0) (8 . "0") (100 . "AcDbLine") (10 0.0 53890.6 0.0) (11 27048.1 53890.6 0.0) (210 0.0 0.0 1.0))
      ((0 . "LINE") (100 . "AcDbEntity") (67 . 0) (8 . "0") (100 . "AcDbLine") (10 0.0 72164.2 0.0) (11 26879.2 72164.2 0.0) (210 0.0 0.0 1.0))
    ))
  ("INT3_EF"
    (
      ((0 . "LINE") (100 . "AcDbEntity") (67 . 0) (8 . "0") (100 . "AcDbLine") (10 0.0 0.0 0.0) (11 0.0 72164.2 0.0) (210 0.0 0.0 1.0))
      ((0 . "LINE") (100 . "AcDbEntity") (67 . 0) (8 . "0") (100 . "AcDbLine") (10 0.0 53890.6 0.0) (11 27048.1 53890.6 0.0) (210 0.0 0.0 1.0))
      ((0 . "LINE") (100 . "AcDbEntity") (67 . 0) (8 . "0") (100 . "AcDbLine") (10 0.0 72164.2 0.0) (11 26879.2 72164.2 0.0) (210 0.0 0.0 1.0))
      ((0 . "LINE") (100 . "AcDbEntity") (67 . 0) (8 . "0") (100 . "AcDbLine") (10 0.0 36082.1 0.0) (11 27137.1 36082.1 0.0) (210 0.0 0.0 1.0))
    ))
  ("INT_COMB"
    (
      ((0 . "LINE") (100 . "AcDbEntity") (67 . 0) (8 . "0") (100 . "AcDbLine") (10 -17673.0 -38246.9 0.0) (11 17091.9 45682.9 0.0) (210 0.0 0.0 1.0))
      ((0 . "LINE") (100 . "AcDbEntity") (67 . 0) (8 . "0") (100 . "AcDbLine") (10 17091.9 45682.9 0.0) (11 40840.0 45682.9 0.0) (210 0.0 0.0 1.0))
      ((0 . "LINE") (100 . "AcDbEntity") (67 . 0) (8 . "0") (100 . "AcDbLine") (10 -17673.0 -38246.9 0.0) (11 -47245.1 -38246.9 0.0) (210 0.0 0.0 1.0))
    ))
  ("INT_COMB_DOBLE"
    (
      ((0 . "LINE") (100 . "AcDbEntity") (67 . 0) (8 . "0") (100 . "AcDbLine") (10 -17679.0 -42680.9 0.0) (11 17738.5 42824.5 0.0) (210 0.0 0.0 1.0))
      ((0 . "LINE") (100 . "AcDbEntity") (67 . 0) (8 . "0") (100 . "AcDbLine") (10 17738.5 42824.5 0.0) (11 42119.1 42824.5 0.0) (210 0.0 0.0 1.0))
      ((0 . "LINE") (100 . "AcDbEntity") (67 . 0) (8 . "0") (100 . "AcDbLine") (10 -17679.0 -42680.9 0.0) (11 -41988.4 -42680.9 0.0) (210 0.0 0.0 1.0))
      ((0 . "LINE") (100 . "AcDbEntity") (67 . 0) (8 . "0") (100 . "AcDbLine") (10 -41616.3 42824.5 0.0) (11 -17798.2 42824.5 0.0) (210 0.0 0.0 1.0))
      ((0 . "LINE") (100 . "AcDbEntity") (67 . 0) (8 . "0") (100 . "AcDbLine") (10 -17798.2 42824.5 0.0) (11 17738.5 -42680.9 0.0) (210 0.0 0.0 1.0))
      ((0 . "LINE") (100 . "AcDbEntity") (67 . 0) (8 . "0") (100 . "AcDbLine") (10 17738.5 -42680.9 0.0) (11 42119.1 -42680.9 0.0) (210 0.0 0.0 1.0))
    ))
  ("INT_ENCH"
    (
      ((0 . "CIRCLE") (100 . "AcDbEntity") (67 . 0) (8 . "0") (100 . "AcDbCircle") (10 27048.1 0.0 0.0) (40 . 27048.1) (210 0.0 0.0 1.0))
      ((0 . "LINE") (100 . "AcDbEntity") (67 . 0) (8 . "0") (100 . "AcDbLine") (10 0.0 0.0 0.0) (11 0.0 53890.6 0.0) (210 0.0 0.0 1.0))
      ((0 . "LINE") (100 . "AcDbEntity") (67 . 0) (8 . "0") (100 . "AcDbLine") (10 0.0 53890.6 0.0) (11 27048.1 53890.6 0.0) (210 0.0 0.0 1.0))
      ((0 . "LINE") (100 . "AcDbEntity") (67 . 0) (8 . "0") (100 . "AcDbLine") (10 66183.6 0.0 0.0) (11 27048.1 0.0 0.0) (210 0.0 0.0 1.0))
      ((0 . "LINE") (100 . "AcDbEntity") (67 . 0) (8 . "0") (100 . "AcDbLine") (10 27048.1 27048.1 0.0) (11 27048.1 -27048.1 0.0) (210 0.0 0.0 1.0))
    ))
  ("MED"
    (
      ((0 . "MTEXT") (100 . "AcDbEntity") (67 . 0) (8 . "0") (100 . "AcDbMText") (10 18203.3 35114.4 0.0) (40 . 16780.7) (41 . 52093.9) (46 . 0.0) (71 . 1) (72 . 5) (1 . "M") (7 . "Standard") (210 0.0 0.0 1.0) (11 1.0 0.0 0.0) (42 . 16013.8) (43 . 16780.7) (50 . 0.0) (73 . 1) (44 . 1.0))
    ))
  ("MTR_CC"
    (
      ((0 . "MTEXT") (100 . "AcDbEntity") (67 . 0) (8 . "0") (100 . "AcDbMText") (10 18203.3 35114.4 0.0) (40 . 16780.7) (41 . 52093.9) (46 . 0.0) (71 . 1) (72 . 5) (1 . "M") (7 . "Standard") (210 0.0 0.0 1.0) (11 1.0 0.0 0.0) (42 . 16013.8) (43 . 16780.7) (50 . 0.0) (73 . 1) (44 . 1.0))
      ((0 . "LINE") (100 . "AcDbEntity") (67 . 0) (8 . "0") (100 . "AcDbLine") (10 14666.5 9418.9 0.0) (11 36949.8 9418.9 0.0) (210 0.0 0.0 1.0))
    ))
  ("MTR_INDUCC"
    (
      ((0 . "ARC") (100 . "AcDbEntity") (67 . 0) (8 . "0") (100 . "AcDbCircle") (10 29922.7 10464.4 0.0) (40 . 3442.51) (210 0.0 0.0 1.0) (100 . "AcDbArc") (50 . 0.210112) (51 . 3.14387))
      ((0 . "ARC") (100 . "AcDbEntity") (67 . 0) (8 . "0") (100 . "AcDbCircle") (10 22944.2 11182.4 0.0) (40 . 3609.76) (210 0.0 0.0 1.0) (100 . "AcDbArc") (50 . 3.139) (51 . 6.08073))
      ((0 . "LINE") (100 . "AcDbEntity") (67 . 0) (8 . "0") (100 . "AcDbLine") (10 19334.4 11182.4 0.0) (11 19334.4 13906.9 0.0) (210 0.0 0.0 1.0))
      ((0 . "LINE") (100 . "AcDbEntity") (67 . 0) (8 . "0") (100 . "AcDbLine") (10 33289.5 11182.4 0.0) (11 33289.5 7572.61 0.0) (210 0.0 0.0 1.0))
      ((0 . "MTEXT") (100 . "AcDbEntity") (67 . 0) (8 . "0") (100 . "AcDbMText") (10 18203.3 40103.6 0.0) (40 . 16780.7) (41 . 52093.9) (46 . 0.0) (71 . 1) (72 . 5) (1 . "M") (7 . "Standard") (210 0.0 0.0 1.0) (11 1.0 0.0 0.0) (42 . 16013.8) (43 . 16780.7) (50 . 0.0) (73 . 1) (44 . 1.0))
    ))
  ("MTR_INDUCC_BOB"
    (
      ((0 . "CIRCLE") (100 . "AcDbEntity") (67 . 0) (8 . "0") (100 . "AcDbCircle") (10 0.0 0.0 0.0) (40 . 32213.5) (210 0.0 0.0 1.0))
    ))
  ("PRTLAMP_MUR_APLQ"
    (
      ((0 . "LINE") (100 . "AcDbEntity") (67 . 0) (8 . "0") (100 . "AcDbLine") (10 -67807.0 1169.17 0.0) (11 -67807.0 24051.2 0.0) (210 0.0 0.0 1.0))
      ((0 . "LINE") (100 . "AcDbEntity") (67 . 0) (8 . "0") (100 . "AcDbLine") (10 -67807.0 24051.2 0.0) (11 -67807.0 -23125.0 0.0) (210 0.0 0.0 1.0))
      ((0 . "LINE") (100 . "AcDbEntity") (67 . 0) (8 . "0") (100 . "AcDbLine") (10 -14209.3 34304.3 0.0) (11 14209.3 -34304.3 0.0) (210 0.0 0.0 1.0))
      ((0 . "LINE") (100 . "AcDbEntity") (67 . 0) (8 . "0") (100 . "AcDbLine") (10 14209.3 34304.3 0.0) (11 -14209.3 -34304.3 0.0) (210 0.0 0.0 1.0))
    ))
  ("PRTLAMP_MUR_INT"
    (
      ((0 . "LINE") (100 . "AcDbEntity") (67 . 0) (8 . "0") (100 . "AcDbLine") (10 -67322.7 0.0 0.0) (11 -67322.7 22882.0 0.0) (210 0.0 0.0 1.0))
      ((0 . "LINE") (100 . "AcDbEntity") (67 . 0) (8 . "0") (100 . "AcDbLine") (10 -67322.7 22882.0 0.0) (11 -67322.7 -24294.2 0.0) (210 0.0 0.0 1.0))
      ((0 . "LINE") (100 . "AcDbEntity") (67 . 0) (8 . "0") (100 . "AcDbLine") (10 -13725.0 33135.2 0.0) (11 14693.6 -35473.5 0.0) (210 0.0 0.0 1.0))
      ((0 . "LINE") (100 . "AcDbEntity") (67 . 0) (8 . "0") (100 . "AcDbLine") (10 14693.6 33135.2 0.0) (11 -13725.0 -35473.5 0.0) (210 0.0 0.0 1.0))
      ((0 . "LINE") (100 . "AcDbEntity") (67 . 0) (8 . "0") (100 . "AcDbLine") (10 14693.6 33135.2 0.0) (11 18940.6 22882.0 0.0) (210 0.0 0.0 1.0))
    ))
  ("PRTLAMP"
    (
      ((0 . "LINE") (100 . "AcDbEntity") (67 . 0) (8 . "0") (100 . "AcDbLine") (10 14209.3 34304.3 0.0) (11 -14209.3 -34304.3 0.0) (210 0.0 0.0 1.0))
    ))
  ("TDA"
    (
      ((0 . "LWPOLYLINE") (100 . "AcDbEntity") (67 . 0) (8 . "0") (100 . "AcDbPolyline") (90 . 4) (70 . 1) (43 . 0.0) (38 . 0.0) (39 . 0.0) (10 -41008.2 26120.6) (40 . 0.0) (41 . 0.0) (42 . 0.0) (91 . 0) (10 41008.2 26120.6) (40 . 0.0) (41 . 0.0) (42 . 0.0) (91 . 0) (10 41008.2 -26120.6) (40 . 0.0) (41 . 0.0) (42 . 0.0) (91 . 0) (10 -41008.2 -26120.6) (40 . 0.0) (41 . 0.0) (42 . 0.0) (91 . 0) (210 0.0 0.0 1.0))
    ))
  ("TC"
    (
      ((0 . "LWPOLYLINE") (100 . "AcDbEntity") (67 . 0) (8 . "0") (100 . "AcDbPolyline") (90 . 4) (70 . 1) (43 . 0.0) (38 . 0.0) (39 . 0.0) (10 -41008.2 26120.6) (40 . 0.0) (41 . 0.0) (42 . 0.0) (91 . 0) (10 41008.2 26120.6) (40 . 0.0) (41 . 0.0) (42 . 0.0) (91 . 0) (10 41008.2 -26120.6) (40 . 0.0) (41 . 0.0) (42 . 0.0) (91 . 0) (10 -41008.2 -26120.6) (40 . 0.0) (41 . 0.0) (42 . 0.0) (91 . 0) (210 0.0 0.0 1.0))
    ))
  ("TABL_FRZAMTRZ"
    (
      ((0 . "LWPOLYLINE") (100 . "AcDbEntity") (67 . 0) (8 . "0") (100 . "AcDbPolyline") (90 . 4) (70 . 1) (43 . 0.0) (38 . 0.0) (39 . 0.0) (10 -41008.2 26120.6) (40 . 0.0) (41 . 0.0) (42 . 0.0) (91 . 0) (10 41008.2 26120.6) (40 . 0.0) (41 . 0.0) (42 . 0.0) (91 . 0) (10 41008.2 -26120.6) (40 . 0.0) (41 . 0.0) (42 . 0.0) (91 . 0) (10 -41008.2 -26120.6) (40 . 0.0) (41 . 0.0) (42 . 0.0) (91 . 0) (210 0.0 0.0 1.0))
    ))
  ("TAB_RAY_X"
    (
      ((0 . "LWPOLYLINE") (100 . "AcDbEntity") (67 . 0) (8 . "0") (100 . "AcDbPolyline") (90 . 4) (70 . 1) (43 . 0.0) (38 . 0.0) (39 . 0.0) (10 -41008.2 26120.6) (40 . 0.0) (41 . 0.0) (42 . 0.0) (91 . 0) (10 41008.2 26120.6) (40 . 0.0) (41 . 0.0) (42 . 0.0) (91 . 0) (10 41008.2 -26120.6) (40 . 0.0) (41 . 0.0) (42 . 0.0) (91 . 0) (10 -41008.2 -26120.6) (40 . 0.0) (41 . 0.0) (42 . 0.0) (91 . 0) (210 0.0 0.0 1.0))
      ((0 . "LINE") (100 . "AcDbEntity") (67 . 0) (8 . "0") (100 . "AcDbLine") (10 -41008.2 -26120.6 0.0) (11 41008.2 26120.6 0.0) (210 0.0 0.0 1.0))
    ))
  ("TABL_EXPEC"
    (
    ))
))

;;; ------------------------------------------------------------
;;; 2. FUNCIONES AUXILIARES
;;; ------------------------------------------------------------

;;; Función para limpiar una entidad de códigos no deseados (para entmake)
(defun limpia-entidad (ent / new)
  (setq new '())
  (foreach par ent
    (cond
      ((member (car par) '(-1 -2 -3)) nil) ; eliminar códigos negativos
      ((= (car par) 5) nil) ; handle
      ((= (car par) 102) nil) ; grupos de reactores (a veces problemáticos)
      ((and (>= (car par) 330) (<= (car par) 369)) nil) ; punteros a otros objetos
      (t (setq new (cons par new)))
    )
  )
  (reverse new)
)

;;; Función para crear todos los bloques a partir de *bloques*
(defun crear-bloques ()
  (foreach bloque *bloques*
    (setq nombre (car bloque))
    (if (not (tblsearch "BLOCK" nombre))
      (progn
        (princ (strcat "\nCreando bloque: " nombre))
        (entmake (list '(0 . "BLOCK") (cons 2 nombre) '(70 . 0) '(10 0.0 0.0 0.0)))
        (foreach ent (cadr bloque)
          (entmake (limpia-entidad ent))
        )
        (entmake '((0 . "ENDBLK")))
      )
    )
  )
  (princ "\nTodos los bloques han sido creados.")
)

;;; Función para seleccionar escala estándar
(defun atx:pick-scale ( / op )
  (princ "\n=== SELECCION DE ESCALA ===")
  (princ "\n 1) Plano de construcción (1.0)")
  (princ "\n 2) Plano de electricidad (0.5)")
  (princ "\n 3) Presentación (2.0)")
  (princ "\n 0) Ingresar escala manualmente")
  (princ "\n=============================")
  (setq op (getint "\nSeleccione opcion [0-3] <1>: "))
  (cond
    ((or (null op) (= op 1)) 1.0)
    ((= op 2) 0.5)
    ((= op 3) 2.0)
    ((= op 0) (getreal "\nIngrese factor de escala: "))
    (T (princ "\nOpción no válida, se usará 1.0") 1.0)
  )
)

;;; ------------------------------------------------------------
;;; 3. COMANDO PRINCIPAL RIC-18
;;; ------------------------------------------------------------
(defun c:RIC-18 ( / i op nombre pt escala rotacion oldAttReq lista-nombres)
  ;; Extraer lista de nombres de los bloques
  (setq lista-nombres (mapcar 'car *bloques*))

  (princ "\n=== MENU DE BLOQUES RIC-18 ===")
  (setq i 1)
  (foreach nombre lista-nombres
    (princ (strcat "\n " (itoa i) ") " nombre))
    (setq i (1+ i))
  )
  (princ "\n 0) Ingresar nombre manualmente")
  (princ "\n================================")

  (setq op (getint (strcat "\nSeleccione opcion [0-" (itoa (length lista-nombres)) "]: ")))
  (cond
    ((null op) (princ "\nOperación cancelada.") (exit))
    ((= op 0) (setq nombre (getstring "\nIngrese nombre del bloque: ")))
    ((and (>= op 1) (<= op (length lista-nombres)))
     (setq nombre (nth (1- op) lista-nombres)))
    (T (princ "\nOpción no válida.") (exit))
  )

  ;; Verificar que el bloque exista (si no, intentar crearlo)
  (if (not (tblsearch "BLOCK" nombre))
    (progn
      (princ (strcat "\nEl bloque \"" nombre "\" no está definido. Intentando crearlo..."))
      ;; Buscar en *bloques* y crearlo
      (setq encontrado nil)
      (foreach bloque *bloques*
        (if (= (car bloque) nombre)
          (progn
            (entmake (list '(0 . "BLOCK") (cons 2 nombre) '(70 . 0) '(10 0.0 0.0 0.0)))
            (foreach ent (cadr bloque)
              (entmake (limpia-entidad ent))
            )
            (entmake '((0 . "ENDBLK")))
            (setq encontrado T)
          )
        )
      )
      (if (not encontrado)
        (progn
          (princ (strcat "\nNo se encontró la definición del bloque \"" nombre "\" en la base de datos."))
          (exit)
        )
        (princ "\nBloque creado.")
      )
    )
  )

  ;; Seleccionar escala estándar
  (setq escala (atx:pick-scale))

  ;; Punto de inserción
  (setq pt (getpoint "\nPunto de inserción: "))
  (if (null pt)
    (progn (princ "\nCancelado.") (exit))
  )

  ;; Rotación
  (setq rotacion (getangle pt "\nRotación <0>: "))
  (if (null rotacion) (setq rotacion 0.0))

  ;; Insertar bloque con atributos desactivados
  (setq oldAttReq (getvar "ATTREQ"))
  (setvar "ATTREQ" 0)
  (command "._-INSERT" nombre pt escala rotacion)
  (while (> (getvar "CMDACTIVE") 0) (command ""))
  (setvar "ATTREQ" oldAttReq)

  (princ "\nBloque insertado.")
  (princ)
)

;;; ------------------------------------------------------------
;;; 4. MENSAJES DE CARGA
;;; ------------------------------------------------------------
(crear-bloques) ; crear los bloques al cargar el programa
(princ "\nComando RIC-18 cargado. Use RIC-18 para insertar bloques.")
(princ)
